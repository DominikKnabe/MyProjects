FME workspace Knabe_Woell_Semesterarbeit.fmw

Parameters:
- SourceDataset_XLSXR = \\fs.univie.ac.at\homedirs\dominikk22\Desktop\FME_Semesterarbeit\Daten Abschlussaufgabe\Ressourcen\Layernames CityGRID.xlsx   # Excel-Tabelle zur Level-Klassifizierung angeben
- FEATURE_TYPES_2 =   # Feature Types to Read
- SourceDataset_XLSXR_3 = \\fs.univie.ac.at\homedirs\dominikk22\Desktop\FME_Semesterarbeit\Daten Abschlussaufgabe\Ressourcen\Fehlercodes.xlsx   # Excel-Tabelle mit Fehlercodes angeben
- SourceDataset_DGNV8 = \\fs.univie.ac.at\homedirs\dominikk22\Desktop\FME_Semesterarbeit\Daten Abschlussaufgabe\Daten\Prüfungsgebiet\Gebiet_07.dgn   # Einzulesendes .dgn File (V8) angeben
- FEATURE_TYPES_3 =   # Feature Types to Read
- DestDataset_DGNV8 = ..\Ergebnis   # Destination Bentley MicroStation Design File

Readers:
- XLSXR_1: XLSXR from $(SourceDataset_XLSXR)
- XLSXR_2: XLSXR from $(SourceDataset_XLSXR_3)
- DGNV8_1: DGNV8 from $(SourceDataset_DGNV8)

Writers:
- DGNV8_2: DGNV8 to $(DestDataset_DGNV8)

Note: Runden auf dritte Nachkommastelle
Note: Layerabgleich nach City-GRID System (Excel-Tabelle beschreibt Namensgebung) (E-31)
CoordinateRounder
    XPREC = 3
    YPREC = 3
    ZPREC = 3
    ROUNDED -> FeatureMerger [REQUESTOR]
Junction_3
    -> Junction_4
Note: E31 Output
Junction_4
    -> Junction_11
Junction_11
    -> FeatureMerger_6 [REQUESTOR]

Bookmark: Daten einlesen
Note: Einlesen des .dgn Files
general roof line (reader DGNV8_1)
    -> CoordinateRounder
Note: Excel File mit Layer-Bezeichnung
Tabelle1 (reader XLSXR_1)
    attributes: Layer_CityGRID char(17), Level_DGN char(18)
    -> FeatureMerger [SUPPLIER]

Bookmark: E-31: Layerabgleich
FeatureMerger
    ATTR_ACCUM_MODE = Merge Supplier
    ATTR_CONFLICT_RES = Use Requestor
    IGNORE_NULLS = No
    JOIN_KEYS = @Value(fme_feature_type) @Value(Level_DGN) AUTO
    MERGE_TYPE = Attributes Only
    PROCESS_DUPS = NO
    REJECT_NULL_MISSING_KEYS = No
    SUPPLIERS_FIRST = No
    MERGED -> AttributeManager
    UNMERGED_REQUESTOR -> AttributeCreator_10
Note: Entfernen überflüssiger Attribute
AttributeManager
    ATTR_TABLE:
      REMOVE fme_feature_type
      REMOVE Level_DGN
    -> Tester_5
    -> Tester
    -> Tester_2
    -> Tester_7
    -> Tester_8
    -> Tester_9
    -> Tester_4
    -> Counter_2
    -> Tester_13
    -> Tester_12
    -> Tester_15
    -> Tester_14
Note: Erstellung Errorcode-ID
AttributeCreator_10
    ATTR_TABLE = SET_TO Errorcode_ = E31
    -> Junction_3

Bookmark: Geometrie-Test
Tester
    BOOL_OP = OR
    TEST_CLAUSE:
      TEST @Value(fme_geometry) = fme_line
      TEST @Value(fme_geometry) = fme_polygon
    TEST_MODE = TEST
    FAILED -> AttributeCreator_9

Bookmark: E_02: Filtern von Linien und Polygonfeatures
Note: Später abspeichern
Note: Erstellung Errorcode-ID
AttributeCreator_9
    ATTR_TABLE = SET_TO Errorcode_ = E02
    -> Junction_11

Bookmark: E-03: Filterung von Polygonen von Inner- und OuterBoundary und Fläche größer 0
Note: Filterung von Elementen mit Eigenschaft "InnerBoundaries" & "OuterBoundary"
Tester_2
    BOOL_OP = OR
    TEST_CLAUSE:
      TEST @Value(Layer_CityGRID) = innerBoundaries
      TEST @Value(Layer_CityGRID) = outerBoundary
    TEST_MODE = TEST
    PASSED -> GeometryCoercer
Note: Überführung von FME_Lines zu FME_Polygon wenn möglich
GeometryCoercer
    GQUERY:
      for $geom in //geometry
      where $geom/count(parent::geometry) = 0
      return number($geom/@fme_id)
    KIND = fme_polygon
    COERCED -> AreaCalculator_2
    UNTOUCHED -> Junction_2
AreaCalculator_2
    AREA_ATTR = _area
    AREA_TYPE = Plane Area
    MULT = 1
    -> Tester_3
Note: Prüfe ob Fläche größer als 0 ist
Tester_3
    BOOL_OP = OR
    TEST_CLAUSE = TEST @Value(_area) != 0
    TEST_MODE = TEST
    FAILED -> Junction_2
Junction_2
    -> AttributeCreator_8
Note: Erstellung Errorcode-ID
AttributeCreator_8
    ATTR_TABLE = SET_TO Errorcode_ = E03
    -> Junction_11

Bookmark: E-04: Es dürfen keine vertikalen Linienabschnitte vorkommen
Note: Filtern von Inner- und OuterBoundary
Tester_7
    BOOL_OP = OR
    TEST_CLAUSE:
      TEST @Value(Layer_CityGRID) = innerBoundaries
      TEST @Value(Layer_CityGRID) = outerBoundary
    TEST_MODE = TEST
    FAILED -> Counter
Note: Zuweisung von Feature-ID
Counter
    CNT_ATTR = _count
    DOMAIN = counter
    SCOPE = Global
    START = 0
    -> Chopper
    -> FeatureMerger_2 [SUPPLIER]
Note: Aufsplatung der Polylines und Polygone in Liniensegmente mit 2 Vertices
Chopper
    DEAGGREGATE_INPUT = Deaggregate
    MAX_VERTICES = 2
    MODE = By Vertex
    REMNANT_ATTR = _remnant
    CHOPPED -> CoordinateExtractor
    UNTOUCHED -> CoordinateExtractor
Note: X&Y von Start- und Endpunkt identisch. Z unterschiedlich
Tester_6
    BOOL_OP = AND
    TEST_CLAUSE:
      TEST @Value(endpunkt_x) = @Value(startpunkt_x)
      TEST @Value(endpunkt_y) = @Value(startpunkt_y)
      TEST @Value(endpunkt_z) != @Value(startpunkt_z)
    TEST_MODE = TEST
    PASSED -> FeatureMerger_2 [REQUESTOR]
Note: Identifizieren der betroffenen Features
FeatureMerger_2
    ATTR_ACCUM_MODE = Merge Supplier
    ATTR_CONFLICT_RES = Use Requestor
    IGNORE_NULLS = No
    JOIN_KEYS = @Value(_count) @Value(_count) AUTO
    MERGE_TYPE = Attributes Only
    PROCESS_DUPS = NO
    REJECT_NULL_MISSING_KEYS = No
    SUPPLIERS_FIRST = No
    MERGED -> AttributeCreator_7
Note: Erstellung Errorcode-ID
AttributeCreator_7
    ATTR_TABLE = SET_TO Errorcode_ = E04
    -> Junction_11

Bookmark: Ermittlung der Koordinaten von Start- und Endpunkt
CoordinateExtractor
    IND = 0
    MODE = Specify Coordinate
    X_ATTR = startpunkt_x
    Y_ATTR = startpunkt_y
    Z_ATTR = startpunkt_z
    -> CoordinateExtractor_2
CoordinateExtractor_2
    IND = -1
    MODE = Specify Coordinate
    X_ATTR = endpunkt_x
    Y_ATTR = endpunkt_y
    Z_ATTR = endpunkt_z
    -> Tester_6

Bookmark: Filtern von Inner- und OuterBoundaries
Tester_5
    BOOL_OP = OR
    TEST_CLAUSE = TEST @Value(Layer_CityGRID) = outerBoundary
    TEST_MODE = TEST
    PASSED -> GeometryCoercer_2
    FAILED -> Counter_5
Tester_4
    BOOL_OP = OR
    TEST_CLAUSE = TEST @Value(Layer_CityGRID) = innerBoundaries
    TEST_MODE = TEST
    PASSED -> GeometryCoercer_3
    FAILED -> Counter_6

Bookmark: Filtern von Polygonen
GeometryCoercer_2
    GQUERY:
      for $geom in //geometry
      where $geom/count(parent::geometry) = 0
      return number($geom/@fme_id)
    KIND = fme_polygon
    COERCED -> Dissolver
GeometryCoercer_3
    GQUERY:
      for $geom in //geometry
      where $geom/count(parent::geometry) = 0
      return number($geom/@fme_id)
    KIND = fme_polygon
    COERCED -> Dissolver_2

Bookmark: Flächen vereinen
Dissolver
    ACCUM_INPUT_ATTRS = Use Attributes From One Feature
    CLEANING_TOLERANCE = Automatic
    CONNECT_Z_MODE = First Wins
    DEAGGREGATE_INPUT = Yes
    AREA -> Clipper_OuterBoundary [CLIPPER]
Dissolver_2
    ACCUM_INPUT_ATTRS = Use Attributes From One Feature
    CLEANING_TOLERANCE = Automatic
    CONNECT_Z_MODE = First Wins
    DEAGGREGATE_INPUT = Yes
    AREA -> Clipper_InnerBoundary [CLIPPER]

Bookmark: E-05: Keine Features außerhalb OuterBoundary und keine Features innerhalb InnerBoundary
Counter_5
    CNT_ATTR = _count
    DOMAIN = counter
    SCOPE = Global
    START = 0
    -> Clipper_OuterBoundary [CANDIDATE]
    -> Junction_7
Note: FeatureMerger_7 : Supplier
Junction_7
    -> Junction_8
Note: Counter_5 : Output
Junction_8
    -> FeatureMerger_7 [SUPPLIER]
Counter_6
    CNT_ATTR = _count
    DOMAIN = counter
    SCOPE = Global
    START = 0
    -> Clipper_InnerBoundary [CANDIDATE]
    -> Junction_5
Note: FeatureMerger_8 : Supplier
Junction_5
    -> Junction_6
Note: Counter_6 : Output
Junction_6
    -> FeatureMerger_8 [SUPPLIER]
Note: Filtern von OuterBoundaries, welche innerhalb von Innerboundaries sind.
Tester_11
    BOOL_OP = OR
    TEST_CLAUSE = TEST @Value(Layer_CityGRID) = outerBoundary
    TEST_MODE = TEST
    FAILED -> Junction
Junction
    -> AttributeCreator_6
Note: Erstellung Errorcode-ID
AttributeCreator_6
    ATTR_TABLE = SET_TO Errorcode_ = E05
    -> Junction_11

Bookmark: Verschneidung der Features mit Inner- und OuterBoundaries
Clipper_OuterBoundary
    BOUNDARY_CASES = BOTH
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> FeatureMerger_7 [REQUESTOR]
    REMNANTS -> Junction
Clipper_InnerBoundary
    BOUNDARY_CASES = INSIDE
    CLEANING_TOLERANCE = Automatic
    CLIPPED_ATTR = _clipped
    CLIPPERS_FIRST = NO
    GENERATE_LIST = NO
    INVALID_PARTS_HANDLING = REJECT_PARTS
    MISSING_M_MODE = Linear Interpolation
    MISSING_Z_MODE = Planar Interpolation
    MULTIPLE_CLIPPERS = YES
    M_VAL_SOURCE = CANDIDATE
    OVERLAPPING_CLIPPERS = CLIP_INTERIM
    PRESERVE_RASTER_EXTENTS = NO
    RASTER_CELL_MODE = CENTER
    Z_VAL_SOURCE = CANDIDATE
    INSIDE -> FeatureMerger_8 [REQUESTOR]

Bookmark: Identifizieren betroffener Features
FeatureMerger_7
    ATTR_ACCUM_MODE = Merge Supplier
    ATTR_CONFLICT_RES = Use Requestor
    IGNORE_NULLS = No
    JOIN_KEYS = @Value(_count) @Value(_count) AUTO
    MERGE_TYPE = Attributes Only
    PROCESS_DUPS = NO
    REJECT_NULL_MISSING_KEYS = No
    SUPPLIERS_FIRST = No
FeatureMerger_8
    ATTR_ACCUM_MODE = Merge Supplier
    ATTR_CONFLICT_RES = Use Requestor
    IGNORE_NULLS = No
    JOIN_KEYS = @Value(_count) @Value(_count) AUTO
    MERGE_TYPE = Attributes Only
    PROCESS_DUPS = NO
    REJECT_NULL_MISSING_KEYS = No
    SUPPLIERS_FIRST = No
    USED_SUPPLIER -> Tester_11

Bookmark: Filtern von Inner- und OuterBoundaries
Tester_13
    BOOL_OP = OR
    TEST_CLAUSE = TEST @Value(Layer_CityGRID) = outerBoundary
    TEST_MODE = TEST
    PASSED -> GeometryCoercer_4
Tester_12
    BOOL_OP = OR
    TEST_CLAUSE = TEST @Value(Layer_CityGRID) = innerBoundaries
    TEST_MODE = TEST
    PASSED -> GeometryCoercer_6

Bookmark: E-06: InnerBoundaries dürfen OuterBoundaries weder schneiden, noch berühren und dürfen nicht außerhalb liegen
Note: Filtern von Polygonen
GeometryCoercer_4
    GQUERY:
      for $geom in //geometry
      where $geom/count(parent::geometry) = 0
      return number($geom/@fme_id)
    KIND = fme_polygon
    COERCED -> Dissolver_3
    COERCED -> SpatialRelator_2 [Supplier]
Note: Flächen vereinen
Dissolver_3
    ACCUM_INPUT_ATTRS = Use Attributes From One Feature
    CLEANING_TOLERANCE = Automatic
    CONNECT_Z_MODE = First Wins
    DEAGGREGATE_INPUT = Yes
    AREA -> Clipper [CLIPPER]
Note: Filtern von Polygonen
GeometryCoercer_6
    GQUERY:
      for $geom in //geometry
      where $geom/count(parent::geometry) = 0
      return number($geom/@fme_id)
    KIND = fme_polygon
    COERCED -> Counter_3
    COERCED -> SpatialRelator_2 [Requestor]
Note: ID-zuweisen
Counter_3
    CNT_ATTR = _count
    DOMAIN = counter
    SCOPE = Global
    START = 0
    -> FeatureMerger_4 [SUPPLIER]
    -> Clipper [CANDIDATE]
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> FeatureMerger_4 [REQUESTOR]
Note: Identifizieren der betroffenen Features
FeatureMerger_4
    ATTR_ACCUM_MODE = Merge Supplier
    ATTR_CONFLICT_RES = Use Requestor
    IGNORE_NULLS = No
    JOIN_KEYS = @Value(_count) @Value(_count) AUTO
    MERGE_TYPE = Attributes Only
    PROCESS_DUPS = NO
    REJECT_NULL_MISSING_KEYS = No
    SUPPLIERS_FIRST = No
    USED_SUPPLIER -> AttributeCreator_5
Note: Erstellung Errorcode-ID
AttributeCreator_5
    ATTR_TABLE = SET_TO Errorcode_ = E06
    -> Junction_11

Bookmark: Überprüfung auf Berührung
Note: Test ob Features sich berühren
SpatialRelator_2
    AGGREGATE_HANDLING = Yes
    CALC_CARD = No
    CURVE_BOUNDARY_RULE_PARAM = Default Rule
    LIST_NAME = _relationships
    PREDICATES = TOUCHES
    SUCCESS_ATTR = _related_suppliers
    -> Tester_19
Note: Identifizieren berührender Features
Tester_19
    BOOL_OP = OR
    TEST_CLAUSE = TEST @Value(_related_suppliers) = 1
    TEST_MODE = TEST
    PASSED -> AttributeCreator_5

Bookmark: Filterung TopLines und BottomLines
Tester_8
    BOOL_OP = OR
    TEST_CLAUSE = TEST @Value(Layer_CityGRID) = breakTopLines
    TEST_MODE = TEST
    PASSED -> Matcher
Tester_9
    BOOL_OP = OR
    TEST_CLAUSE = TEST @Value(Layer_CityGRID) = breakBottomLines
    TEST_MODE = TEST
    PASSED -> Matcher

Bookmark: E-07: Check ob TopLines und BottomLines 2D-identisch sind
Note: Prüfe ob 2D-identisch
Matcher
    CHECK_COORDINATE_SYSTEMS = No
    CNT_ATTR = _match_id
    LENIENT_MATCH = No
    MATCH = 2D
    NOT_MATCHED -> AttributeCreator_4
Note: Erstellung Errorcode-ID
AttributeCreator_4
    ATTR_TABLE = SET_TO Errorcode_ = E07
    -> Junction_11

Bookmark: E-09: Prüfe ob Features 3D-Koordinaten aufweisen
Note: Zuweisung Feature-ID
Counter_2
    CNT_ATTR = _count
    DOMAIN = counter
    SCOPE = Global
    START = 0
    -> Chopper_2
    -> FeatureMerger_3 [SUPPLIER]
Note: Aufsplitten in einzelne Vertices
Chopper_2
    DEAGGREGATE_INPUT = Deaggregate
    MAX_VERTICES = 1
    MODE = By Vertex
    REMNANT_ATTR = _remnant
    CHOPPED -> CoordinateExtractor_3
Note: Koordinaten der Vertices berechnen
CoordinateExtractor_3
    LIST_NAME = _indices
    MODE = All Coordinates
    -> Tester_10
Note: Filtern von 3D- Koordinaren
Tester_10
    BOOL_OP = OR
    TEST_CLAUSE = TEST @Value(_indices{0}.z) > 0
    TEST_MODE = TEST
    FAILED -> FeatureMerger_3 [REQUESTOR]
Note: Identifizieren der 2D-Features
FeatureMerger_3
    ATTR_ACCUM_MODE = Merge Supplier
    ATTR_CONFLICT_RES = Use Requestor
    IGNORE_NULLS = No
    JOIN_KEYS = @Value(_count) @Value(_count) AUTO
    MERGE_TYPE = Attributes Only
    PROCESS_DUPS = NO
    REJECT_NULL_MISSING_KEYS = No
    SUPPLIERS_FIRST = No
    USED_SUPPLIER -> AttributeCreator_3
Note: Erstellung Errorcode-ID
AttributeCreator_3
    ATTR_TABLE = SET_TO Errorcode_ = E09
    -> Junction_11

Bookmark: Filtern von Inner- und OuterBoundaries
Tester_15
    BOOL_OP = OR
    TEST_CLAUSE = TEST @Value(Layer_CityGRID) = outerBoundary
    TEST_MODE = TEST
    PASSED -> GeometryCoercer_5
Tester_14
    BOOL_OP = OR
    TEST_CLAUSE = TEST @Value(Layer_CityGRID) = innerBoundaries
    TEST_MODE = TEST
    PASSED -> SpatialRelator [Supplier]

Bookmark: E-28: Innerhalb eines outerBoundary Features dürfen keine weiteren outerBoundary Features liegen, es sei denn dazwischen liegt ein innerBoundary Feature. OuterBoundary Features dürfen sich nicht überlappen.
Note: Filtern von Polygonen
GeometryCoercer_5
    GQUERY:
      for $geom in //geometry
      where $geom/count(parent::geometry) = 0
      return number($geom/@fme_id)
    KIND = fme_polygon
    COERCED -> DonutBuilder
    COERCED -> Counter_4
Note: Bilden von Donuts. OuterBoundary innerhalb von OuterBoundary
DonutBuilder
    CONNECT_Z_MODE = First Wins
    DROP = no
    FLAG_ATTR = _hole_flag
    AREA -> Tester_16
Note: Filtern der inneren OuterBoundaries
Tester_16
    BOOL_OP = OR
    TEST_CLAUSE = TEST @Value(_hole_flag) = yes
    TEST_MODE = TEST
    PASSED -> SpatialRelator [Requestor]
Note: OuterBoundary innerhalb InnerBoundary?
SpatialRelator
    AGGREGATE_HANDLING = Yes
    CALC_CARD = No
    CURVE_BOUNDARY_RULE_PARAM = Default Rule
    LIST_NAME = _relationships
    PREDICATES = WITHIN
    SUCCESS_ATTR = _related_suppliers
    -> Tester_17
Note: Filtern der OuterBoundaries, die nicht innerhalb einer InnerBoundary liegen
Tester_17
    BOOL_OP = OR
    TEST_CLAUSE = TEST @Value(_related_suppliers) = 0
    TEST_MODE = TEST
    PASSED -> Junction_9
Junction_9
    -> AttributeCreator_2
Note: Erstellung Errorcode-ID
AttributeCreator_2
    ATTR_TABLE = SET_TO Errorcode_ = E28
    -> Junction_11

Bookmark: Prüfe auf Überlappung
Note: Zuweisung Feature-ID
Counter_4
    CNT_ATTR = _count
    DOMAIN = counter
    SCOPE = Global
    START = 0
    -> AreaOnAreaOverlayer_2 [AREA]
    -> FeatureMerger_5 [SUPPLIER]
Note: Überlappungen berechnen
AreaOnAreaOverlayer_2
    ACCUM_ATTRS_NAME = Use Attributes From One Feature
    CLEANING_TOLERANCE = 0.001
    CONNECT_Z_MODE = First Wins
    DEAGGREGATE_INPUT = Yes
    OVC_ATTR = _overlaps
    AREA -> Tester_18
Note: Filtern von Flächen mit Überlappung
Tester_18
    BOOL_OP = OR
    TEST_CLAUSE = TEST @Value(_overlaps) > 1
    TEST_MODE = TEST
    PASSED -> FeatureMerger_5 [REQUESTOR]
FeatureMerger_5
    ATTR_ACCUM_MODE = Merge Supplier
    ATTR_CONFLICT_RES = Use Requestor
    IGNORE_NULLS = No
    JOIN_KEYS = @Value(_count) @Value(_count) AUTO
    MERGE_TYPE = Attributes Only
    PROCESS_DUPS = NO
    REJECT_NULL_MISSING_KEYS = No
    SUPPLIERS_FIRST = No
    USED_SUPPLIER -> Junction_9

Bookmark: Speichervorgang
Note: Einlesen der Fehlercodes
Tabelle1 (reader XLSXR_2)
    attributes: Errorcode char(4), Priority number(3,0), Type char(8), Description char(76), Bsp char(44), F string
    -> FeatureMerger_6 [SUPPLIER]
Note: Vereinigung der Excel-Tabelle mit Features
FeatureMerger_6
    ATTR_ACCUM_MODE = Merge Supplier
    ATTR_CONFLICT_RES = Use Requestor
    IGNORE_NULLS = No
    JOIN_KEYS = @Value(Errorcode_) @Value(Errorcode) STRING
    MERGE_TYPE = Attributes Only
    PROCESS_DUPS = NO
    REJECT_NULL_MISSING_KEYS = No
    SUPPLIERS_FIRST = No
    MERGED -> FilenamePartExtractor
Note: Extrahieren des Namen des Datensatzes
FilenamePartExtractor
    DIRPATH_ATTR = _dirpath
    EXTENSION_ATTR = _extension
    FULLNAME_ATTR = _filename
    ROOTNAME_ATTR = _rootname
    SRC_ATTR = @Value(fme_basename)
    -> AttributeCreator
Note: Erstellung des LevelNames
AttributeCreator
    ATTR_TABLE = SET_TO Levels = @Value(Priority)_@Value(Errorcode_)_@Value(Description)
    -> Sorter
Note: Sortieren nach Priorität
Sorter
    SORT_PARM = Priority NUMERIC ASCENDING
    SORTED -> AttributeKeeper
Note: Entfernen überflüssiger Attribute
AttributeKeeper
    CREATE_BULK_MODE_FEATURES = NO
    KEEP_ATTRS = Layer_CityGRID,Levels,_rootname
    -> DGNStyler
Note: Einfärben der Fehler
DGNStyler
    CELL_MODE_DISPLAY = Shared (V8 Only)
    CELL_MODE_RELATIVE = No
    CELL_ROT = 0
    CELL_SIZETYPE_DISPLAY = Master Units
    CELL_SIZEX = 1.0
    CELL_SIZEY = 1.0
    COLOR_BY_LEVEL_DISPLAY = Yes (V8 Only)
    COLOR_CHOICE_DISPLAY = RGB
    LINE_STYLE = 0
    LINE_WEIGHT = ByLevel
    RGB_COLOR = 0.666667,0,0
    DGNStyled -> Level1 (writer DGNV8_2)
Level1 (writer DGNV8_2)
